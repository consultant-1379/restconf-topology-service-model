module ietf-trans-client-svc-types {
  namespace "urn:ietf:params:xml:ns:yang:ietf-trans-client-svc-types";
  prefix clntsvc-types;

  organization
    "Internet Engineering Task Force (IETF) CCAMP WG";
  contact
    "
      ID-draft editor:
        Haomian Zheng (zhenghaomian@huawei.com);
        Aihua Guo (aihuaguo.ietf@gmail.com);
        Italo Busi (italo.busi@huawei.com);
        Anton Snitser (asnizar@cisco.com);
        Francesco Lazzeri (francesco.lazzeri@ericsson.com);
    ";
  description
    "This module defines a YANG data model for describing
     transport network client types. The model fully conforms
     to the Network Management Datastore Architecture (NMDA).

     Copyright (c) 2019 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  revision 2019-11-03 {
    description
      "version -01 as a WG document";
    reference
      "draft-ietf-ccamp-client-signal-yang";
  }

  identity direction {
    description
      "Direction information of Client Signal.";
  }

  identity bidirectional {
    base direction;
    description
      "Client Signal is bi-directional.";
  }

  identity unidirectional {
    base direction;
    description
      "Client Signal is uni-directional.";
  }
}
