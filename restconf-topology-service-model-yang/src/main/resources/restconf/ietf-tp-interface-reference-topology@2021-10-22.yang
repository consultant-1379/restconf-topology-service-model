module ietf-tp-interface-reference-topology {
  yang-version 1.1;
  namespace "urn:ietf:params:xml:ns:yang:ietf-tp-interface-reference-topology";
  prefix ifref;

  import ietf-network {
    prefix nw;
    reference
      "RFC 8345: A YANG Data Model for Network Topologies";
  }
  import ietf-network-topology {
    prefix nt;
    reference
      "RFC 8345: A YANG Data Model for Network Topologies";
  }
  import ietf-te-topology {
    prefix tet;
    reference
      "RFC 8795: YANG Data Model for Traffic Engineering
       (TE) Topologies";
  }
  import ietf-interfaces {
    prefix if;
    reference
      "RFC 8343";
  }

  organization
    "Internet Engineering Task Force (IETF) CCAMP WG";
  contact
    "WG List: <mailto:ccamp@ietf.org>

     //[JonasA] Who would like to be on the list of editors/contributors?
     Editor: Jonas Ahlberg
             <mailto:jonas.ahlberg@ericsson.com>
     Editor: Scott Mansfield
             <mailto:scott.mansfield@ericsson.com>
     Editor: Min Ye
             <mailto:amy.yemin@huawei.com>
     Editor: Italo Busi
             <mailto:Italo.Busi@huawei.com>
     Editor: Xi Li
             <mailto:Xi.Li@neclab.eu>
     Editor: Daniela Spreafico
              <mailto:daniela.spreafico@nokia.com>
    ";

  // Note to RFC Editor: replace XXXX with actual RFC number and
  // remove this note.

  description
    "This is a module for defining a reference from a termination
     point in a te topology to a list element in interfaces
     as defined in RFC 8343.

     Copyright (c) 2020 IETF Trust and the persons identified as
     authors of the code.  All rights reserved.
     Redistribution and use in source and binary forms, with or
     without modification, is permitted pursuant to, and subject to
     the license terms contained in, the Simplified BSD License set
     forth in Section 4.c of the IETF Trust's Legal Provisions
     Relating to IETF Documents
     (http://trustee.ietf.org/license-info).
     This version of this YANG module is part of RFC XXXX
     (https://tools.ietf.org/html/rfcXXXX); see the RFC itself for
     full legal notices.";

  revision 2021-10-22 {
    description
      "First rough draft.";
    reference
      "";
  }

  /*
   * Groupings
   */

  grouping tp-to-interface-ref {
    description
      "Grouping used for reference between a termination point and
       an interface.";
    leaf tp-to-interface-path {
      type leafref {
        path "/if:interfaces/if:interface/if:name";
      }
      description
        "Leafref expression referencing a list element, identified
         by its name, in interfaces as defined in RFC 8343.";
    }
  }

  /*
   * Data nodes
   */

  augment "/nw:networks/nw:network/nw:node/nt:termination-point/"
        + "tet:te" {
    description
      "Augmentation to add possibility to reference an element
       in the list of interfaces as defined by RFC 8343.";
    uses tp-to-interface-ref;
  }
}
