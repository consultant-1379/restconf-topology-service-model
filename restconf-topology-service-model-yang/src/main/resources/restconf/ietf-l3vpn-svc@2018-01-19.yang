module ietf-l3vpn-svc {
  yang-version 1.1;
  namespace "urn:ietf:params:xml:ns:yang:ietf-l3vpn-svc";
  prefix l3vpn-svc;

  import ietf-inet-types {
    prefix inet;
  }
  import ietf-yang-types {
    prefix yang;
  }
  import ietf-netconf-acm {
    prefix nacm;
  }

  organization
    "IETF L3SM Working Group";
  contact
    "WG List: <mailto:l3sm@ietf.org>
     Editor:
      L3SM WG
     Chairs:
      Adrian Farrel, Qin Wu
    ";
  description
    "This YANG module defines a generic service configuration
     model for Layer 3 VPNs. This model is common across all
     vendor implementations.
     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of RFC 8299; see
     the RFC itself for full legal notices.";

  revision 2018-01-19 {
    description
      "Revision of RFC 8049 to fix implementation issues.";
    reference
      "RFC 8299";
  }
  revision 2017-01-27 {
    description
      "Initial document.";
    reference
      "RFC 8049.";
  }

  /* Features */

  feature cloud-access {
    description
      "Allows the VPN to connect to a CSP.";
  }

  feature multicast {
    description
      "Enables multicast capabilities in a VPN.";
  }

  feature ipv4 {
    description
      "Enables IPv4 support in a VPN.";
  }

  feature ipv6 {
    description
      "Enables IPv6 support in a VPN.";
  }

  feature lan-tag {
    description
      "Enables LAN Tag support in a VPN Policy filter.";
  }

  feature carrierscarrier {
    description
      "Enables support of CsC.";
  }

  feature extranet-vpn {
    description
      "Enables support of extranet VPNs.";
  }

  feature site-diversity {
    description
      "Enables support of site diversity constraints.";
  }

  feature encryption {
    description
      "Enables support of encryption.";
  }

  feature qos {
    description
      "Enables support of classes of services.";
  }

  feature qos-custom {
    description
      "Enables support of the custom QoS profile.";
  }

  feature rtg-bgp {
    description
      "Enables support of the BGP routing protocol.";
  }

  feature rtg-rip {
    description
      "Enables support of the RIP routing protocol.";
  }

  feature rtg-ospf {
    description
      "Enables support of the OSPF routing protocol.";
  }

  feature rtg-ospf-sham-link {
    description
      "Enables support of OSPF sham links.";
  }

  feature rtg-vrrp {
    description
      "Enables support of the VRRP routing protocol.";
  }

  feature fast-reroute {
    description
      "Enables support of Fast Reroute.";
  }

  feature bfd {
    description
      "Enables support of BFD.";
  }

  feature always-on {
    description
      "Enables support of the 'always-on' access constraint.";
  }

  feature requested-type {
    description
      "Enables support of the 'requested-type' access constraint.";
  }

  feature bearer-reference {
    description
      "Enables support of the 'bearer-reference' access constraint.";
  }

  feature target-sites {
    description
      "Enables support of the 'target-sites' match flow parameter.";
  }

  /* Typedefs */

  typedef svc-id {
    type string;
    description
      "Defines a type of service component identifier.";
  }

  typedef template-id {
    type string;
    description
      "Defines a type of service template identifier.";
  }

  typedef address-family {
    type enumeration {
      enum ipv4 {
        description
          "IPv4 address family.";
      }
      enum ipv6 {
        description
          "IPv6 address family.";
      }
    }
    description
      "Defines a type for the address family.";
  }

  /* Identities */

  identity site-network-access-type {
    description
      "Base identity for site-network-access type.";
  }

  identity point-to-point {
    base site-network-access-type;
    description
      "Identity for point-to-point connection.";
  }

  identity multipoint {
    base site-network-access-type;
    description
      "Identity for multipoint connection.
       Example: Ethernet broadcast segment.";
  }

  identity placement-diversity {
    description
      "Base identity for site placement constraints.";
  }

  identity bearer-diverse {
    base placement-diversity;
    description
      "Identity for bearer diversity.
       The bearers should not use common elements.";
  }

  identity pe-diverse {
    base placement-diversity;
    description
      "Identity for PE diversity.";
  }

  identity pop-diverse {
    base placement-diversity;
    description
      "Identity for POP diversity.";
  }

  identity linecard-diverse {
    base placement-diversity;
    description
      "Identity for linecard diversity.";
  }

  identity same-pe {
    base placement-diversity;
    description
      "Identity for having sites connected on the same PE.";
  }

  identity same-bearer {
    base placement-diversity;
    description
      "Identity for having sites connected using the same bearer.";
  }

  identity customer-application {
    description
      "Base identity for customer application.";
  }

  identity web {
    base customer-application;
    description
      "Identity for Web application (e.g., HTTP, HTTPS).";
  }

  identity mail {
    base customer-application;
    description
      "Identity for mail application.";
  }

  identity file-transfer {
    base customer-application;
    description
      "Identity for file transfer application (e.g., FTP, SFTP).";
  }

  identity database {
    base customer-application;
    description
      "Identity for database application.";
  }

  identity social {
    base customer-application;
    description
      "Identity for social-network application.";
  }

  identity games {
    base customer-application;
    description
      "Identity for gaming application.";
  }

  identity p2p {
    base customer-application;
    description
      "Identity for peer-to-peer application.";
  }

  identity network-management {
    base customer-application;
    description
      "Identity for management application
       (e.g., Telnet, syslog, SNMP).";
  }

  identity voice {
    base customer-application;
    description
      "Identity for voice application.";
  }

  identity video {
    base customer-application;
    description
      "Identity for video conference application.";
  }

  identity embb {
    base customer-application;
    description
      "Identity for an enhanced Mobile Broadband (eMBB)
       application.  Note that an eMBB application demands
       network performance with a wide variety of
       characteristics, such as data rate, latency,
       loss rate, reliability, and many other parameters.";
  }

  identity urllc {
    base customer-application;
    description
      "Identity for an Ultra-Reliable and Low Latency
       Communications (URLLC) application.  Note that a
       URLLC application demands network performance
       with a wide variety of characteristics, such as latency,
       reliability, and many other parameters.";
  }

  identity mmtc {
    base customer-application;
    description
      "Identity for a massive Machine Type
       Communications (mMTC) application.  Note that an
       mMTC application demands network performance
       with a wide variety of characteristics, such as data
       rate, latency, loss rate, reliability, and many
       other parameters.";
  }

  identity site-vpn-flavor {
    description
      "Base identity for the site VPN service flavor.";
  }

  identity site-vpn-flavor-single {
    base site-vpn-flavor;
    description
      "Base identity for the site VPN service flavor.
       Used when the site belongs to only one VPN.";
  }

  identity site-vpn-flavor-multi {
    base site-vpn-flavor;
    description
      "Base identity for the site VPN service flavor.
       Used when a logical connection of a site
       belongs to multiple VPNs.";
  }

  identity site-vpn-flavor-sub {
    base site-vpn-flavor;
    description
      "Base identity for the site VPN service flavor.
       Used when a site has multiple logical connections.
       Each connection may belong to different multiple VPNs.";
  }

  identity site-vpn-flavor-nni {
    base site-vpn-flavor;
    description
      "Base identity for the site VPN service flavor.
       Used to describe an NNI option A connection.";
  }

  identity management {
    description
      "Base identity for site management scheme.";
  }

  identity co-managed {
    base management;
    description
      "Base identity for co-managed site.";
  }

  identity customer-managed {
    base management;
    description
      "Base identity for customer-managed site.";
  }

  identity provider-managed {
    base management;
    description
      "Base identity for provider-managed site.";
  }

  identity address-allocation-type {
    description
      "Base identity for address-allocation-type for PE-CE link.";
  }

  identity provider-dhcp {
    base address-allocation-type;
    description
      "Provider network provides DHCP service to customer.";
  }

  identity provider-dhcp-relay {
    base address-allocation-type;
    description
      "Provider network provides DHCP relay service to customer.";
  }

  identity provider-dhcp-slaac {
    base address-allocation-type;
    description
      "Provider network provides DHCP service to customer,
       as well as SLAAC.";
  }

  identity static-address {
    base address-allocation-type;
    description
      "Provider-to-customer addressing is static.";
  }

  identity slaac {
    base address-allocation-type;
    description
      "Use IPv6 SLAAC.";
  }

  identity site-role {
    description
      "Base identity for site type.";
  }

  identity any-to-any-role {
    base site-role;
    description
      "Site in an any-to-any IP VPN.";
  }

  identity spoke-role {
    base site-role;
    description
      "Spoke site in a Hub-and-Spoke IP VPN.";
  }

  identity hub-role {
    base site-role;
    description
      "Hub site in a Hub-and-Spoke IP VPN.";
  }

  identity vpn-topology {
    description
      "Base identity for VPN topology.";
  }

  identity any-to-any {
    base vpn-topology;
    description
      "Identity for any-to-any VPN topology.";
  }

  identity hub-spoke {
    base vpn-topology;
    description
      "Identity for Hub-and-Spoke VPN topology.";
  }

  identity hub-spoke-disjoint {
    base vpn-topology;
    description
      "Identity for Hub-and-Spoke VPN topology
       where Hubs cannot communicate with each other.";
  }

  identity multicast-tree-type {
    description
      "Base identity for multicast tree type.";
  }

  identity ssm-tree-type {
    base multicast-tree-type;
    description
      "Identity for SSM tree type.";
  }

  identity asm-tree-type {
    base multicast-tree-type;
    description
      "Identity for ASM tree type.";
  }

  identity bidir-tree-type {
    base multicast-tree-type;
    description
      "Identity for bidirectional tree type.";
  }

  identity multicast-rp-discovery-type {
    description
      "Base identity for RP discovery type.";
  }

  identity auto-rp {
    base multicast-rp-discovery-type;
    description
      "Base identity for Auto-RP discovery type.";
  }

  identity static-rp {
    base multicast-rp-discovery-type;
    description
      "Base identity for static type.";
  }

  identity bsr-rp {
    base multicast-rp-discovery-type;
    description
      "Base identity for BSR discovery type.";
  }

  identity routing-protocol-type {
    description
      "Base identity for routing protocol type.";
  }

  identity ospf {
    base routing-protocol-type;
    description
      "Identity for OSPF protocol type.";
  }

  identity bgp {
    base routing-protocol-type;
    description
      "Identity for BGP protocol type.";
  }

  identity static {
    base routing-protocol-type;
    description
      "Identity for static routing protocol type.";
  }

  identity rip {
    base routing-protocol-type;
    description
      "Identity for RIP protocol type.";
  }

  identity vrrp {
    base routing-protocol-type;
    description
      "Identity for VRRP protocol type.
       This is to be used when LANs are directly connected
       to PE routers.";
  }

  identity direct {
    base routing-protocol-type;
    description
      "Identity for direct protocol type.";
  }

  identity protocol-type {
    description
      "Base identity for protocol field type.";
  }

  identity tcp {
    base protocol-type;
    description
      "TCP protocol type.";
  }

  identity udp {
    base protocol-type;
    description
      "UDP protocol type.";
  }

  identity icmp {
    base protocol-type;
    description
      "ICMP protocol type.";
  }

  identity icmp6 {
    base protocol-type;
    description
      "ICMPv6 protocol type.";
  }

  identity gre {
    base protocol-type;
    description
      "GRE protocol type.";
  }

  identity ipip {
    base protocol-type;
    description
      "IP-in-IP protocol type.";
  }

  identity hop-by-hop {
    base protocol-type;
    description
      "Hop-by-Hop IPv6 header type.";
  }

  identity routing {
    base protocol-type;
    description
      "Routing IPv6 header type.";
  }

  identity esp {
    base protocol-type;
    description
      "ESP header type.";
  }

  identity ah {
    base protocol-type;
    description
      "AH header type.";
  }

  identity vpn-policy-filter-type {
    description
      "Base identity for VPN Policy filter type.";
  }

  identity ipv4 {
    base vpn-policy-filter-type;
    description
      "Identity for IPv4 Prefix filter type.";
  }

  identity ipv6 {
    base vpn-policy-filter-type;
    description
      "Identity for IPv6 Prefix filter type.";
  }

  identity lan {
    base vpn-policy-filter-type;
    description
      "Identity for LAN Tag filter type.";
  }

  identity qos-profile-direction {
    description
      "Base identity for QoS profile direction.";
  }

  identity site-to-wan {
    base qos-profile-direction;
    description
      "Identity for Site-to-WAN direction.";
  }

  identity wan-to-site {
    base qos-profile-direction;
    description
      "Identity for WAN-to-Site direction.";
  }

  identity both {
    base qos-profile-direction;
    description
      "Identity for both WAN-to-Site direction
       and Site-to-WAN direction.";
  }

  /* Groupings */

  grouping vpn-service-cloud-access {
    container cloud-accesses {
      if-feature "cloud-access";
      list cloud-access {
        key "cloud-identifier";
        leaf cloud-identifier {
          type leafref {
            path "/l3vpn-svc/vpn-profiles/"
               + "valid-provider-identifiers/cloud-identifier/id";
          }
          description
            "Identification of cloud service.
             Local administration meaning.";
        }
        choice list-flavor {
          case permit-any {
            leaf permit-any {
              type empty;
              description
                "Allows all sites.";
            }
          }
          case deny-any-except {
            leaf-list permit-site {
              type leafref {
                path "/l3vpn-svc/sites/site/site-id";
              }
              description
                "Site ID to be authorized.";
            }
          }
          case permit-any-except {
            leaf-list deny-site {
              type leafref {
                path "/l3vpn-svc/sites/site/site-id";
              }
              description
                "Site ID to be denied.";
            }
          }
          description
            "Choice for cloud access policy.  By
             default, all sites in the IP VPN MUST
             be authorized to access the cloud.";
        }
        container address-translation {
          container nat44 {
            leaf enabled {
              type boolean;
              default "false";
              description
                "Controls whether or not Network address
                 translation from IPv4 to IPv4 (NAT44)
                 [RFC3022] is required.";
            }
            leaf nat44-customer-address {
              type inet:ipv4-address;
              description
                "Address to be used for network address
                 translation from IPv4 to IPv4.  This is
                 to be used if the customer is providing
                 the IPv4 address.  If the customer address
                           is not set, the model assumes that the
                 provider will allocate the address.";
            }
            description
              "IPv4-to-IPv4 translation.";
          }
          description
            "Container for NAT.";
        }
        description
          "Cloud access configuration.";
      }
      description
        "Container for cloud access configurations.";
    }
    description
      "Grouping for VPN cloud definition.";
  }

  grouping multicast-rp-group-cfg {
    choice group-format {
      mandatory true;
      case singleaddress {
        leaf group-address {
          type inet:ip-address;
          description
            "A single multicast group address.";
        }
      }
      case startend {
        leaf group-start {
          type inet:ip-address;
          description
            "The first multicast group address in
             the multicast group address range.";
        }
        leaf group-end {
          type inet:ip-address;
          description
            "The last multicast group address in
             the multicast group address range.";
        }
      }
      description
        "Choice for multicast group format.";
    }
    description
      "This grouping defines multicast group or
       multicast groups for RP-to-group mapping.";
  }

  grouping vpn-service-multicast {
    container multicast {
      if-feature "multicast";
      leaf enabled {
        type boolean;
        default "false";
        description
          "Enables multicast.";
      }
      container customer-tree-flavors {
        leaf-list tree-flavor {
          type identityref {
            base multicast-tree-type;
          }
          description
            "Type of tree to be used.";
        }
        description
          "Type of trees used by customer.";
      }
      container rp {
        container rp-group-mappings {
          list rp-group-mapping {
            key "id";
            leaf id {
              type uint16;
              description
                "Unique identifier for the mapping.";
            }
            container provider-managed {
              leaf enabled {
                type boolean;
                default "false";
                description
                  "Set to true if the Rendezvous Point (RP)
                   must be a provider-managed node.  Set to false
                   if it is a customer-managed node.";
              }
              leaf rp-redundancy {
                type boolean;
                default "false";
                description
                  "If true, a redundancy mechanism for the RP
                   is required.";
              }
              leaf optimal-traffic-delivery {
                type boolean;
                default "false";
                description
                  "If true, the SP must ensure that
                   traffic uses an optimal path.  An SP may use
                   Anycast RP or RP-tree-to-SPT switchover
                   architectures.";
              }
              description
                "Parameters for a provider-managed RP.";
            }
            leaf rp-address {
              when "../provider-managed/enabled = 'false'" {
                description
                  "Relevant when the RP is not provider-managed.";
              }
              type inet:ip-address;
              mandatory true;
              description
                "Defines the address of the RP.
                 Used if the RP is customer-managed.";
            }
            container groups {
              list group {
                key "id";
                leaf id {
                  type uint16;
                  description
                    "Identifier for the group.";
                }
                uses multicast-rp-group-cfg;
                description
                  "List of multicast groups.";
              }
              description
                "Multicast groups associated with the RP.";
            }
            description
              "List of RP-to-group mappings.";
          }
          description
            "RP-to-group mappings parameters.";
        }
        container rp-discovery {
          leaf rp-discovery-type {
            type identityref {
              base multicast-rp-discovery-type;
            }
            default "static-rp";
            description
              "Type of RP discovery used.";
          }
          container bsr-candidates {
            when "derived-from-or-self(../rp-discovery-type, "
               + "'l3vpn-svc:bsr-rp')" {
              description
                "Only applicable if discovery type
                 is BSR-RP.";
            }
            leaf-list bsr-candidate-address {
              type inet:ip-address;
              description
                "Address of BSR candidate.";
            }
            description
              "Container for List of Customer
               BSR candidate's addresses.";
          }
          description
            "RP discovery parameters.";
        }
        description
          "RP parameters.";
      }
      description
        "Multicast global parameters for the VPN service.";
    }
    description
      "Grouping for multicast VPN definition.";
  }

  grouping vpn-service-mpls {
    leaf carrierscarrier {
      if-feature "carrierscarrier";
      type boolean;
      default "false";
      description
        "The VPN is using CsC, and so MPLS is required.";
    }
    description
      "Grouping for MPLS CsC definition.";
  }

  grouping customer-location-info {
    container locations {
      list location {
        key "location-id";
        leaf location-id {
          type svc-id;
          description
            "Identifier for a particular location.";
        }
        leaf address {
          type string;
          description
            "Address (number and street) of the site.";
        }
        leaf postal-code {
          type string;
          description
            "Postal code of the site.";
        }
        leaf state {
          type string;
          description
            "State of the site.  This leaf can also be
             used to describe a region for a country that
             does not have states.";
        }
        leaf city {
          type string;
          description
            "City of the site.";
        }
        leaf country-code {
          type string {
            pattern '[A-Z]{2}';
          }
          description
            "Country of the site.
             Expressed as ISO ALPHA-2 code.";
        }
        description
          "Location of the site.";
      }
      description
        "List of locations for the site.";
    }
    description
      "This grouping defines customer location parameters.";
  }

  grouping site-group {
    container groups {
      list group {
        key "group-id";
        leaf group-id {
          type string;
          description
            "Group-id the site belongs to.";
        }
        description
          "List of group-ids.";
      }
      description
        "Groups the site or site-network-access belongs to.";
    }
    description
      "Grouping definition to assign
       group-ids to site or site-network-access.";
  }

  grouping site-diversity {
    container site-diversity {
      if-feature "site-diversity";
      uses site-group;
      description
        "Diversity constraint type.  All
         site-network-accesses will inherit
         the group values defined here.";
    }
    description
      "This grouping defines site
       diversity parameters.";
  }

  grouping access-diversity {
    container access-diversity {
      if-feature "site-diversity";
      uses site-group;
      container constraints {
        list constraint {
          key "constraint-type";
          leaf constraint-type {
            type identityref {
              base placement-diversity;
            }
            description
              "Diversity constraint type.";
          }
          container target {
            choice target-flavor {
              default "id";
              case id {
                list group {
                  key "group-id";
                  leaf group-id {
                    type string;
                    description
                      "The constraint will be applied against
                       this particular group-id for this site
                       network access level.";
                  }
                  description
                    "List of group-ids associated with one specific
                     constraint for this site network access level.";
                }
              }
              case all-accesses {
                leaf all-other-accesses {
                  type empty;
                  description
                    "The constraint will be applied against
                     all other site network accesses of this site.";
                }
              }
              case all-groups {
                leaf all-other-groups {
                  type empty;
                  description
                    "The constraint will be applied against
                     all other groups managed by the customer.";
                }
              }
              description
                "Choice for the target flavor definition.";
            }
            description
              "The constraint will be applied against a
               Specific target, and the target can be a list
               of group-ids,all other site network accesses of
               this site, or all other groups managed by the
               customer.";
          }
          description
            "List of constraints.";
        }
        description
          "Placement constraints for this site network access.";
      }
      description
        "Diversity parameters.";
    }
    description
      "This grouping defines access diversity parameters.";
  }

  grouping operational-requirements {
    leaf requested-site-start {
      type yang:date-and-time;
      description
        "Optional leaf indicating requested date and
         time when the service at a particular site is
         expected to start.";
    }
    leaf requested-site-stop {
      type yang:date-and-time;
      description
        "Optional leaf indicating requested date and
         time when the service at a particular site is
         expected to stop.";
    }
    description
      "This grouping defines some operational
       parameters.";
  }

  grouping operational-requirements-ops {
    leaf actual-site-start {
      type yang:date-and-time;
      config false;
      description
        "Optional leaf indicating actual date and
         time when the service at a particular site
         actually started.";
    }
    leaf actual-site-stop {
      type yang:date-and-time;
      config false;
      description
        "Optional leaf indicating actual date and
         time when the service at a particular site
         actually stopped.";
    }
    description
      "This grouping defines some operational
       parameters.";
  }

  grouping flow-definition {
    container match-flow {
      leaf dscp {
        type inet:dscp;
        description
          "DSCP value.";
      }
      leaf dot1p {
        type uint8 {
          range "0..7";
        }
        description
          "802.1p matching.";
      }
      leaf ipv4-src-prefix {
        type inet:ipv4-prefix;
        description
          "Match on IPv4 src address.";
      }
      leaf ipv6-src-prefix {
        type inet:ipv6-prefix;
        description
          "Match on IPv6 src address.";
      }
      leaf ipv4-dst-prefix {
        type inet:ipv4-prefix;
        description
          "Match on IPv4 dst address.";
      }
      leaf ipv6-dst-prefix {
        type inet:ipv6-prefix;
        description
          "Match on IPv6 dst address.";
      }
      leaf l4-src-port {
        type inet:port-number;
        must 'current() < ../l4-src-port-range/lower-port or '
           + 'current() > ../l4-src-port-range/upper-port' {
          description
            "If l4-src-port and l4-src-port-range/lower-port and
             upper-port are set at the same time, l4-src-port
             should not overlap with l4-src-port-range.";
        }
        description
          "Match on Layer 4 src port.";
      }
      leaf-list target-sites {
        if-feature "target-sites";
        type svc-id;
        description
          "Identify a site as traffic destination.";
      }
      container l4-src-port-range {
        leaf lower-port {
          type inet:port-number;
          description
            "Lower boundary for port.";
        }
        leaf upper-port {
          type inet:port-number;
          must '. >= ../lower-port' {
            description
              "Upper boundary for port.  If it
               exists, the upper boundary must be
               higher than the lower boundary.";
          }
          description
            "Upper boundary for port.";
        }
        description
          "Match on Layer 4 src port range.  When
           only the lower-port is present, it represents
           a single port.  When both the lower-port and
           upper-port are specified, it implies
           a range inclusive of both values.";
      }
      leaf l4-dst-port {
        type inet:port-number;
        must 'current() < ../l4-dst-port-range/lower-port or '
           + 'current() > ../l4-dst-port-range/upper-port' {
          description
            "If l4-dst-port and l4-dst-port-range/lower-port
             and upper-port are set at the same time,
             l4-dst-port should not overlap with
             l4-src-port-range.";
        }
        description
          "Match on Layer 4 dst port.";
      }
      container l4-dst-port-range {
        leaf lower-port {
          type inet:port-number;
          description
            "Lower boundary for port.";
        }
        leaf upper-port {
          type inet:port-number;
          must '. >= ../lower-port' {
            description
              "Upper boundary must be
               higher than lower boundary.";
          }
          description
            "Upper boundary for port.  If it exists,
             upper boundary must be higher than lower
             boundary.";
        }
        description
          "Match on Layer 4 dst port range.  When only
           lower-port is present, it represents a single
           port.  When both lower-port and upper-port are
           specified, it implies a range inclusive of both
           values.";
      }
      leaf protocol-field {
        type union {
          type uint8;
          type identityref {
            base protocol-type;
          }
        }
        description
          "Match on IPv4 protocol or IPv6 Next Header field.";
      }
      description
        "Describes flow-matching criteria.";
    }
    description
      "Flow definition based on criteria.";
  }

  grouping site-service-basic {
    leaf svc-input-bandwidth {
      type uint64;
      units "bps";
      mandatory true;
      description
        "From the customer site's perspective, the service
         input bandwidth of the connection or download
         bandwidth from the SP to the site.";
    }
    leaf svc-output-bandwidth {
      type uint64;
      units "bps";
      mandatory true;
      description
        "From the customer site's perspective, the service
         output bandwidth of the connection or upload
         bandwidth from the site to the SP.";
    }
    leaf svc-mtu {
      type uint16;
      units "bytes";
      mandatory true;
      description
        "MTU at service level.  If the service is IP,
         it refers to the IP MTU.  If CsC is enabled,
         the requested 'svc-mtu' leaf will refer to the
         MPLS MTU and not to the IP MTU.";
    }
    description
      "Defines basic service parameters for a site.";
  }

  grouping site-protection {
    container traffic-protection {
      if-feature "fast-reroute";
      leaf enabled {
        type boolean;
        default "false";
        description
          "Enables traffic protection of access link.";
      }
      description
        "Fast Reroute service parameters for the site.";
    }
    description
      "Defines protection service parameters for a site.";
  }

  grouping site-service-mpls {
    container carrierscarrier {
      if-feature "carrierscarrier";
      leaf signalling-type {
        type enumeration {
          enum ldp {
            description
              "Use LDP as the signalling protocol
               between the PE and the CE.  In this case,
               an IGP routing protocol must also be activated.";
          }
          enum bgp {
            description
              "Use BGP (as per RFC 8277) as the signalling protocol
               between the PE and the CE.
               In this case, BGP must also be configured as
               the routing protocol.";
          }
        }
        default "bgp";
        description
          "MPLS signalling type.";
      }
      description
        "This container is used when the customer provides
         MPLS-based services.  This is only used in the case
         of CsC (i.e., a customer builds an MPLS service using
         an IP VPN to carry its traffic).";
    }
    description
      "Defines MPLS service parameters for a site.";
  }

  grouping site-service-qos-profile {
    container qos {
      if-feature "qos";
      container qos-classification-policy {
        list rule {
          key "id";
          ordered-by user;
          leaf id {
            type string;
            description
              "A description identifying the
               qos-classification-policy rule.";
          }
          choice match-type {
            default "match-flow";
            case match-flow {
              uses flow-definition;
            }
            case match-application {
              leaf match-application {
                type identityref {
                  base customer-application;
                }
                description
                  "Defines the application to match.";
              }
            }
            description
              "Choice for classification.";
          }
          leaf target-class-id {
            type string;
            description
              "Identification of the class of service.
               This identifier is internal to the administration.";
          }
          description
            "List of marking rules.";
        }
        description
          "Configuration of the traffic classification policy.";
      }
      container qos-profile {
        choice qos-profile {
          description
            "Choice for QoS profile.
             Can be standard profile or customized profile.";
          case standard {
            description
              "Standard QoS profile.";
            leaf profile {
              type leafref {
                path "/l3vpn-svc/vpn-profiles/valid-provider-identifiers"
                   + "/qos-profile-identifier/id";
              }
              description
                "QoS profile to be used.";
            }
          }
          case custom {
            description
              "Customized QoS profile.";
            container classes {
              if-feature "qos-custom";
              list class {
                key "class-id";
                leaf class-id {
                  type string;
                  description
                    "Identification of the class of service.
                     This identifier is internal to the
                     administration.";
                }
                leaf direction {
                  type identityref {
                    base qos-profile-direction;
                  }
                  default "both";
                  description
                    "The direction to which the QoS profile
                     is applied.";
                }
                leaf rate-limit {
                  type decimal64 {
                    fraction-digits 5;
                    range "0..100";
                  }
                  units "percent";
                  description
                    "To be used if the class must be rate-limited.
                     Expressed as percentage of the service
                     bandwidth.";
                }
                container latency {
                  choice flavor {
                    case lowest {
                      leaf use-lowest-latency {
                        type empty;
                        description
                          "The traffic class should use the path with the
                           lowest latency.";
                      }
                    }
                    case boundary {
                      leaf latency-boundary {
                        type uint16;
                        units "msec";
                        default "400";
                        description
                          "The traffic class should use a path with a
                           defined maximum latency.";
                      }
                    }
                    description
                      "Latency constraint on the traffic class.";
                  }
                  description
                    "Latency constraint on the traffic class.";
                }
                container jitter {
                  choice flavor {
                    case lowest {
                      leaf use-lowest-jitter {
                        type empty;
                        description
                          "The traffic class should use the path with the
                           lowest jitter.";
                      }
                    }
                    case boundary {
                      leaf latency-boundary {
                        type uint32;
                        units "usec";
                        default "40000";
                        description
                          "The traffic class should use a path with a
                           defined maximum jitter.";
                      }
                    }
                    description
                      "Jitter constraint on the traffic class.";
                  }
                  description
                    "Jitter constraint on the traffic class.";
                }
                container bandwidth {
                  leaf guaranteed-bw-percent {
                    type decimal64 {
                      fraction-digits 5;
                      range "0..100";
                    }
                    units "percent";
                    mandatory true;
                    description
                      "To be used to define the guaranteed bandwidth
                       as a percentage of the available service bandwidth.";
                  }
                  leaf end-to-end {
                    type empty;
                    description
                      "Used if the bandwidth reservation
                       must be done on the MPLS network too.";
                  }
                  description
                    "Bandwidth constraint on the traffic class.";
                }
                description
                  "List of classes of services.";
              }
              description
                "Container for list of classes of services.";
            }
          }
        }
        description
          "QoS profile configuration.";
      }
      description
        "QoS configuration.";
    }
    description
      "This grouping defines QoS parameters for a site.";
  }

  grouping site-security-authentication {
    container authentication {
      description
        "Authentication parameters.";
    }
    description
      "This grouping defines authentication parameters for a site.";
  }

  grouping site-security-encryption {
    container encryption {
      if-feature "encryption";
      leaf enabled {
        type boolean;
        default "false";
        description
          "If true, traffic encryption on the connection is required.";
      }
      leaf layer {
        when "../enabled = 'true'" {
          description
            "Require a value for layer when enabled is true.";
        }
        type enumeration {
          enum layer2 {
            description
              "Encryption will occur at Layer 2.";
          }
          enum layer3 {
            description
              "Encryption will occur at Layer 3.
               For example, IPsec may be used when
               a customer requests Layer 3 encryption.";
          }
        }
        description
          "Layer on which encryption is applied.";
      }
      container encryption-profile {
        choice profile {
          case provider-profile {
            leaf profile-name {
              type leafref {
                path "/l3vpn-svc/vpn-profiles/valid-provider-identifiers"
                   + "/encryption-profile-identifier/id";
              }
              description
                "Name of the SP profile to be applied.";
            }
          }
          case customer-profile {
            leaf algorithm {
              type string;
              description
                "Encryption algorithm to be used.";
            }
            choice key-type {
              default "psk";
              case psk {
                leaf preshared-key {
                  type string;
                  description
                    "Pre-Shared Key (PSK) coming from the customer.";
                }
              }
              description
                "Type of keys to be used.";
            }
          }
          description
            "Choice of encryption profile.  The encryption
             profile can be the provider profile or customer profile.";
        }
        description
          "Profile of encryption to be applied.";
      }
      description
        "Encryption parameters.";
    }
    description
      "This grouping defines encryption parameters for a site.";
  }

  grouping site-attachment-bearer {
    container bearer {
      container requested-type {
        if-feature "requested-type";
        leaf requested-type {
          type string;
          description
            "Type of requested bearer: Ethernet, DSL,
             Wireless, etc. Operator specific.";
        }
        leaf strict {
          type boolean;
          default "false";
          description
            "Defines whether requested-type is a preference
               or a strict requirement.";
        }
        description
          "Container for requested-type.";
      }
      leaf always-on {
        if-feature "always-on";
        type boolean;
        default "true";
        description
          "Request for an always-on access type.
           For example, this could mean no dial access type.";
      }
      leaf bearer-reference {
        if-feature "bearer-reference";
        type string;
        description
          "This is an internal reference for the SP.";
      }
      description
        "Bearer-specific parameters.
         To be augmented.";
    }
    description
      "Defines physical properties of a site attachment.";
  }

  grouping site-routing {
    container routing-protocols {
      list routing-protocol {
        key "type";
        leaf type {
          type identityref {
            base routing-protocol-type;
          }
          description
            "Type of routing protocol.";
        }
        container ospf {
          when "derived-from-or-self(../type, 'l3vpn-svc:ospf')" {
            description
              "Only applies when protocol is OSPF.";
          }
          if-feature "rtg-ospf";
          leaf-list address-family {
            type address-family;
            min-elements 1;
            description
              "If OSPF is used on this site, this node
                   contains a configured value.  This node
                   contains at least one address family
                   to be activated.";
          }
          leaf area-address {
            type yang:dotted-quad;
            mandatory true;
            description
              "Area address.";
          }
          leaf metric {
            type uint16;
            default "1";
            description
              "Metric of the PE-CE link.  It is used
               in the routing state calculation and
               path selection.";
          }
          container sham-links {
            if-feature "rtg-ospf-sham-link";
            list sham-link {
              key "target-site";
              leaf target-site {
                type svc-id;
                description
                  "Target site for the sham link connection.
                   The site is referred to by its ID.";
              }
              leaf metric {
                type uint16;
                default "1";
                description
                  "Metric of the sham link.  It is used in
                   the routing state calculation and path
                   selection.  The default value is set
                   to 1.";
              }
              description
                "Creates a sham link with another site.";
            }
            description
              "List of sham links.";
          }
          description
            "OSPF-specific configuration.";
        }
        container bgp {
          when "derived-from-or-self(../type, 'l3vpn-svc:bgp')" {
            description
              "Only applies when protocol is BGP.";
          }
          if-feature "rtg-bgp";
          leaf autonomous-system {
            type uint32;
            mandatory true;
            description
              "Customer AS number in case the customer
               requests BGP routing.";
          }
          leaf-list address-family {
            type address-family;
            min-elements 1;
            description
              "If BGP is used on this site, this node
               contains a configured value.  This node
               contains at least one address family
               to be activated.";
          }
          description
            "BGP-specific configuration.";
        }
        container static {
          when "derived-from-or-self(../type, 'l3vpn-svc:static')" {
            description
              "Only applies when protocol is static.
               BGP activation requires the SP to know
               the address of the customer peer.  When
               BGP is enabled, the 'static-address'
               allocation type for the IP connection
               MUST be used.";
          }
          container cascaded-lan-prefixes {
            list ipv4-lan-prefixes {
              if-feature "ipv4";
              key "lan next-hop";
              leaf lan {
                type inet:ipv4-prefix;
                description
                  "LAN prefixes.";
              }
              leaf lan-tag {
                type string;
                description
                  "Internal tag to be used in VPN policies.";
              }
              leaf next-hop {
                type inet:ipv4-address;
                description
                  "Next-hop address to use on the customer side.";
              }
              description
                "List of LAN prefixes for the site.";
            }
            list ipv6-lan-prefixes {
              if-feature "ipv6";
              key "lan next-hop";
              leaf lan {
                type inet:ipv6-prefix;
                description
                  "LAN prefixes.";
              }
              leaf lan-tag {
                type string;
                description
                  "Internal tag to be used in VPN policies.";
              }
              leaf next-hop {
                type inet:ipv6-address;
                description
                  "Next-hop address to use on the customer side.";
              }
              description
                "List of LAN prefixes for the site.";
            }
            description
              "LAN prefixes from the customer.";
          }
          description
            "Configuration specific to static routing.";
        }
        container rip {
          when "derived-from-or-self(../type, 'l3vpn-svc:rip')" {
            description
              "Only applies when the protocol is RIP.  For IPv4,
               the model assumes that RIP version 2 is used.";
          }
          if-feature "rtg-rip";
          leaf-list address-family {
            type address-family;
            min-elements 1;
            description
              "If RIP is used on this site, this node
               contains a configured value.  This node
                        contains at least one address family
               to be activated.";
          }
          description
            "Configuration specific to RIP routing.";
        }
        container vrrp {
          when "derived-from-or-self(../type, 'l3vpn-svc:vrrp')" {
            description
              "Only applies when protocol is VRRP.";
          }
          if-feature "rtg-vrrp";
          leaf-list address-family {
            type address-family;
            min-elements 1;
            description
              "If VRRP is used on this site, this node
               contains a configured value.  This node contains
               at least one address family to be activated.";
          }
          description
            "Configuration specific to VRRP routing.";
        }
        description
          "List of routing protocols used on
           the site.  This list can be augmented.";
      }
      description
        "Defines routing protocols.";
    }
    description
      "Grouping for routing protocols.";
  }

  grouping site-attachment-ip-connection {
    container ip-connection {
      container ipv4 {
        if-feature "ipv4";
        leaf address-allocation-type {
          type identityref {
            base address-allocation-type;
          }
          must "not(derived-from-or-self(current(), 'l3vpn-svc:slaac') or "
             + "derived-from-or-self(current(), "
             + "'l3vpn-svc:provider-dhcp-slaac'))" {
            error-message "SLAAC is only applicable to IPv6";
          }
          description
            "Defines how addresses are allocated.
                 If there is no value for the address
             allocation type, then IPv4 is not enabled.";
        }
        container provider-dhcp {
          when "derived-from-or-self(../address-allocation-type, "
             + "'l3vpn-svc:provider-dhcp')" {
            description
              "Only applies when addresses are allocated by DHCP.";
          }
          leaf provider-address {
            type inet:ipv4-address;
            description
              "Address of provider side.  If provider-address is not
               specified, then prefix length should not be specified
               either.  It also implies provider-dhcp allocation is
               not enabled.  If provider-address is specified, then
               the prefix length may or may not be specified.";
          }
          leaf prefix-length {
            type uint8 {
              range "0..32";
            }
            must '(../provider-address)' {
              error-message
                "If the prefix length is specified, provider-address
                 must also be specified.";
              description
                "If the prefix length is specified, provider-address
                 must also be specified.";
            }
            description
              "Subnet prefix length expressed in bits.
               If not specified, or specified as zero,
               this means the customer leaves the actual
               prefix length value to the provider.";
          }
          choice address-assign {
            default "number";
            case number {
              leaf number-of-dynamic-address {
                type uint16;
                default "1";
                description
                  "Describes the number of IP addresses
                   the customer requires.";
              }
            }
            case explicit {
              container customer-addresses {
                list address-group {
                  key "group-id";
                  leaf group-id {
                    type string;
                    description
                      "Group-id for the address range from
                       start-address to end-address.";
                  }
                  leaf start-address {
                    type inet:ipv4-address;
                    description
                      "First address.";
                  }
                  leaf end-address {
                    type inet:ipv4-address;
                    description
                      "Last address.";
                  }
                  description
                    "Describes IP addresses allocated by DHCP.
                     When only start-address or only end-address
                     is present, it represents a single address.
                     When both start-address and end-address are
                     specified, it implies a range inclusive of both
                     addresses.  If no address is specified, it implies
                     customer addresses group is not supported.";
                }
                description
                  "Container for customer addresses is allocated by DHCP.";
              }
            }
            description
              "Choice for the way to assign addresses.";
          }
          description
            "DHCP allocated addresses related parameters.";
        }
        container dhcp-relay {
          when "derived-from-or-self(../address-allocation-type, "
             + "'l3vpn-svc:provider-dhcp-relay')" {
            description
              "Only applies when provider is required to implement
               DHCP relay function.";
          }
          leaf provider-address {
            type inet:ipv4-address;
            description
              "Address of provider side.  If provider-address is not
               specified, then prefix length should not be specified
               either.  It also implies provider-dhcp allocation is
               not enabled.  If provider-address is specified, then
               prefix length may or may not be specified.";
          }
          leaf prefix-length {
            type uint8 {
              range "0..32";
            }
            must '(../provider-address)' {
              error-message
                "If prefix length is specified, provider-address
                 must also be specified.";
              description
                "If prefix length is specified, provider-address
                 must also be specified.";
            }
            description
              "Subnet prefix length expressed in bits.  If not
               specified, or specified as zero, this means the
               customer leaves the actual prefix length value
               to the provider.";
          }
          container customer-dhcp-servers {
            leaf-list server-ip-address {
              type inet:ipv4-address;
              description
                "IP address of customer DHCP server.";
            }
            description
              "Container for list of customer DHCP servers.";
          }
          description
            "DHCP relay provided by operator.";
        }
        container addresses {
          when "derived-from-or-self(../address-allocation-type, "
             + "'l3vpn-svc:static-address')" {
            description
              "Only applies when protocol allocation type is static.";
          }
          leaf provider-address {
            type inet:ipv4-address;
            description
              "IPv4 Address List of the provider side.
               When the protocol allocation type is static,
               the provider address must be configured.";
          }
          leaf customer-address {
            type inet:ipv4-address;
            description
              "IPv4 Address of customer side.";
          }
          leaf prefix-length {
            type uint8 {
              range "0..32";
            }
            description
              "Subnet prefix length expressed in bits.
               It is applied to both provider-address
               and customer-address.";
          }
          description
            "Describes IPv4 addresses used.";
        }
        description
          "IPv4-specific parameters.";
      }
      container ipv6 {
        if-feature "ipv6";
        leaf address-allocation-type {
          type identityref {
            base address-allocation-type;
          }
          description
            "Defines how addresses are allocated.
             If there is no value for the address
             allocation type, then IPv6 is
             not enabled.";
        }
        container provider-dhcp {
          when "derived-from-or-self(../address-allocation-type, "
             + "'l3vpn-svc:provider-dhcp') "
             + "or derived-from-or-self(../address-allocation-type, "
             + "'l3vpn-svc:provider-dhcp-slaac')" {
            description
              "Only applies when addresses are allocated by DHCP.";
          }
          leaf provider-address {
            type inet:ipv6-address;
            description
              "Address of the provider side.  If provider-address
               is not specified, then prefix length should not be
               specified either.  It also implies provider-dhcp
                  \t allocation is not enabled.  If provider-address is
               specified, then prefix length may or may
               not be specified.";
          }
          leaf prefix-length {
            type uint8 {
              range "0..128";
            }
            must '(../provider-address)' {
              error-message
                "If prefix length is specified, provider-address
                 must also be specified.";
              description
                "If prefix length is specified, provider-address
                 must also be specified.";
            }
            description
              "Subnet prefix length expressed in bits.  If not
               specified, or specified as zero, this means the
               customer leaves the actual prefix length value
               to the provider.";
          }
          choice address-assign {
            default "number";
            case number {
              leaf number-of-dynamic-address {
                type uint16;
                default "1";
                description
                  "Describes the number of IP addresses the customer
                   requires.";
              }
            }
            case explicit {
              container customer-addresses {
                list address-group {
                  key "group-id";
                  leaf group-id {
                    type string;
                    description
                      "Group-id for the address range from
                       start-address to end-address.";
                  }
                  leaf start-address {
                    type inet:ipv6-address;
                    description
                      "First address.";
                  }
                  leaf end-address {
                    type inet:ipv6-address;
                    description
                      "Last address.";
                  }
                  description
                    "Describes IP addresses allocated by DHCP.  When only
                     start-address or only end-address is present, it
                     represents a single address.  When both start-address
                     and end-address are specified, it implies a range
                     inclusive of both addresses.  If no address is
                     specified, it implies customer addresses group is
                     not supported.";
                }
                description
                  "Container for customer addresses allocated by DHCP.";
              }
            }
            description
              "Choice for the way to assign addresses.";
          }
          description
            "DHCP allocated addresses related parameters.";
        }
        container dhcp-relay {
          when "derived-from-or-self(../address-allocation-type, "
             + "'l3vpn-svc:provider-dhcp-relay')" {
            description
              "Only applies when the provider is required
               to implement DHCP relay function.";
          }
          leaf provider-address {
            type inet:ipv6-address;
            description
              "Address of the provider side.  If provider-address is
               not specified, then prefix length should not be
               specified either.  It also implies provider-dhcp
               allocation is not enabled.  If provider address
               is specified, then prefix length may or may
               not be specified.";
          }
          leaf prefix-length {
            type uint8 {
              range "0..128";
            }
            must '(../provider-address)' {
              error-message
                "If prefix length is specified, provider-address
                    \t  must also be specified.";
              description
                "If prefix length is specified, provider-address
                 must also be specified.";
            }
            description
              "Subnet prefix length expressed in bits.  If not
               specified, or specified as zero, this means the
               customer leaves the actual prefix length value
               to the provider.";
          }
          container customer-dhcp-servers {
            leaf-list server-ip-address {
              type inet:ipv6-address;
              description
                "This node contains the IP address of
                 the customer DHCP server.  If the DHCP relay
                 function is implemented by the
                 provider, this node contains the
                 configured value.";
            }
            description
              "Container for list of customer DHCP servers.";
          }
          description
            "DHCP relay provided by operator.";
        }
        container addresses {
          when "derived-from-or-self(../address-allocation-type, "
             + "'l3vpn-svc:static-address')" {
            description
              "Only applies when protocol allocation type is static.";
          }
          leaf provider-address {
            type inet:ipv6-address;
            description
              "IPv6 Address of the provider side.  When the protocol
               allocation type is static, the provider address
               must be configured.";
          }
          leaf customer-address {
            type inet:ipv6-address;
            description
              "The IPv6 Address of the customer side.";
          }
          leaf prefix-length {
            type uint8 {
              range "0..128";
            }
            description
              "Subnet prefix length expressed in bits.
               It is applied to both provider-address and
               customer-address.";
          }
          description
            "Describes IPv6 addresses used.";
        }
        description
          "IPv6-specific parameters.";
      }
      container oam {
        container bfd {
          if-feature "bfd";
          leaf enabled {
            type boolean;
            default "false";
            description
              "If true, BFD activation is required.";
          }
          choice holdtime {
            default "fixed";
            case fixed {
              leaf fixed-value {
                type uint32;
                units "msec";
                description
                  "Expected BFD holdtime expressed in msec.  The customer
                   may impose some fixed values for the holdtime period
                   if the provider allows the customer use this function.
                   If the provider doesn't allow the customer to use this
                   function, the fixed-value will not be set.";
              }
            }
            case profile {
              leaf profile-name {
                type leafref {
                  path "/l3vpn-svc/vpn-profiles/valid-provider-identifiers/"
                     + "bfd-profile-identifier/id";
                }
                description
                  "Well-known SP profile name.  The provider can propose
                   some profiles to the customer, depending on the service
                   level the customer wants to achieve.  Profile names
                   must be communicated to the customer.";
              }
              description
                "Well-known SP profile.";
            }
            description
              "Choice for holdtime flavor.";
          }
          description
            "Container for BFD.";
        }
        description
          "Defines the Operations, Administration, and Maintenance (OAM)
           mechanisms used on the connection.  BFD is set as a fault
           detection mechanism, but the 'oam' container can easily
           be augmented by other mechanisms";
      }
      description
        "Defines connection parameters.";
    }
    description
      "This grouping defines IP connection parameters.";
  }

  grouping site-service-multicast {
    container multicast {
      if-feature "multicast";
      leaf multicast-site-type {
        type enumeration {
          enum receiver-only {
            description
              "The site only has receivers.";
          }
          enum source-only {
            description
              "The site only has sources.";
          }
          enum source-receiver {
            description
              "The site has both sources and receivers.";
          }
        }
        default "source-receiver";
        description
          "Type of multicast site.";
      }
      container multicast-address-family {
        leaf ipv4 {
          if-feature "ipv4";
          type boolean;
          default "false";
          description
            "Enables IPv4 multicast.";
        }
        leaf ipv6 {
          if-feature "ipv6";
          type boolean;
          default "false";
          description
            "Enables IPv6 multicast.";
        }
        description
          "Defines protocol to carry multicast.";
      }
      leaf protocol-type {
        type enumeration {
          enum host {
            description
              "Hosts are directly connected to the provider network.
               Host protocols such as IGMP or MLD are required.";
          }
          enum router {
            description
              "Hosts are behind a customer router.
               PIM will be implemented.";
          }
          enum both {
            description
              "Some hosts are behind a customer router, and
               some others are directly connected to the
               provider network.  Both host and routing protocols
               must be used.  Typically, IGMP and PIM will be
               implemented.";
          }
        }
        default "both";
        description
          "Multicast protocol type to be used with the customer site.";
      }
      description
        "Multicast parameters for the site.";
    }
    description
      "Multicast parameters for the site.";
  }

  grouping site-management {
    container management {
      leaf type {
        type identityref {
          base management;
        }
        mandatory true;
        description
          "Management type of the connection.";
      }
      description
        "Management configuration.";
    }
    description
      "Management parameters for the site.";
  }

  grouping site-devices {
    container devices {
      when "derived-from-or-self(../management/type, "
         + "'l3vpn-svc:provider-managed') or "
         + "derived-from-or-self(../management/type, 'l3vpn-svc:co-managed')" {
        description
          "Applicable only for provider-managed or
           co-managed device.";
      }
      list device {
        key "device-id";
        leaf device-id {
          type svc-id;
          description
            "Identifier for the device.";
        }
        leaf location {
          type leafref {
            path "../../../locations/"
               + "location/location-id";
          }
          mandatory true;
          description
            "Location of the device.";
        }
        container management {
          when "derived-from-or-self(../../../management/type,"
             + "'l3vpn-svc:co-managed')" {
            description
              "Applicable only for co-managed device.";
          }
          leaf address-family {
            type address-family;
            description
              "Address family used for management.";
          }
          leaf address {
            when '(../address-family)' {
              description
                "If address-family is specified, then address should
                 also be specified.  If address-family is not specified,
                 then address should also not be specified.";
            }
            type inet:ip-address;
            mandatory true;
            description
              "Management address.";
          }
          description
            "Management configuration.  Applicable only for
             co-managed device.";
        }
        description
          "List of devices requested by customer.";
      }
      description
        "Device configuration.";
    }
    description
      "Grouping for device allocation.";
  }

  grouping site-vpn-flavor {
    leaf site-vpn-flavor {
      type identityref {
        base site-vpn-flavor;
      }
      default "site-vpn-flavor-single";
      description
        "Defines the way the VPN multiplexing is done, e.g., whether
         the site belongs to a single VPN site or a multiVPN; or, in the case
         of a multiVPN, whether the logical accesses of the sites belong
         to the same set of VPNs or each logical access maps to
         different VPNs.";
    }
    description
      "Grouping for site VPN flavor.";
  }

  grouping site-vpn-policy {
    container vpn-policies {
      list vpn-policy {
        key "vpn-policy-id";
        leaf vpn-policy-id {
          type svc-id;
          description
            "Unique identifier for the VPN policy.";
        }
        list entries {
          key "id";
          leaf id {
            type svc-id;
            description
              "Unique identifier for the policy entry.";
          }
          container filters {
            list filter {
              key "type";
              ordered-by user;
              leaf type {
                type identityref {
                  base vpn-policy-filter-type;
                }
                description
                  "Type of VPN Policy filter.";
              }
              leaf-list lan-tag {
                when "derived-from-or-self(../type, 'l3vpn-svc:lan')" {
                  description
                    "Only applies when the VPN Policy filter is a
                     LAN Tag filter.";
                }
                if-feature "lan-tag";
                type string;
                description
                  "List of 'lan-tag' items to be matched.  LAN Tag
                   is an Internal tag to be used in VPN policies ";
              }
              leaf-list ipv4-lan-prefix {
                when "derived-from-or-self(../type, 'l3vpn-svc:ipv4')" {
                  description
                    "Only applies when VPN Policy filter is IPv4 Prefix filter.";
                }
                if-feature "ipv4";
                type inet:ipv4-prefix;
                description
                  "List of IPv4 prefixes as LAN Prefixes to be matched.";
              }
              leaf-list ipv6-lan-prefix {
                when "derived-from-or-self(../type, 'l3vpn-svc:ipv6')" {
                  description
                    "Only applies when VPN Policy filter is IPv6 Prefix filter.";
                }
                if-feature "ipv6";
                type inet:ipv6-prefix;
                description
                  "List of IPv6 prefixes as LAN prefixes to be matched.";
              }
              description
                "List of filters used on the site.  This list can
                 be augmented.";
            }
            description
              "If a more-granular VPN attachment is necessary, filtering can
               be used.  If used, it permits the splitting of site LANs among
               multiple VPNs.  The Site LAN can be split based on either LAN
               Tag or LAN prefix.  If no filter is used, all the LANs will be
               part of the same VPNs with the same role.";
          }
          list vpn {
            key "vpn-id";
            leaf vpn-id {
              type leafref {
                path "/l3vpn-svc/vpn-services/"
                   + "vpn-service/vpn-id";
              }
              mandatory true;
              description
                "Reference to an IP VPN.";
            }
            leaf site-role {
              type identityref {
                base site-role;
              }
              default "any-to-any-role";
              description
                "Role of the site in the IP VPN.";
            }
            description
              "List of VPNs the LAN is associated with.";
          }
          description
            "List of entries for export policy.";
        }
        description
          "List of VPN policies.";
      }
      description
        "VPN policy.";
    }
    description
      "VPN policy parameters for the site.";
  }

  grouping site-maximum-routes {
    container maximum-routes {
      list address-family {
        key "af";
        leaf af {
          type address-family;
          description
            "Address family.";
        }
        leaf maximum-routes {
          type uint32;
          description
            "Maximum prefixes the VRF can accept
             for this address family.";
        }
        description
          "List of address families.";
      }
      description
        "Defines 'maximum-routes' for the VRF.";
    }
    description
      "Defines 'maximum-routes' for the site.";
  }

  grouping site-security {
    container security {
      uses site-security-authentication;
      uses site-security-encryption;
      description
        "Site-specific security parameters.";
    }
    description
      "Grouping for security parameters.";
  }

  grouping site-service {
    container service {
      uses site-service-qos-profile;
      uses site-service-mpls;
      uses site-service-multicast;
      description
        "Service parameters on the attachment.";
    }
    description
      "Grouping for service parameters.";
  }

  grouping site-network-access-service {
    container service {
      uses site-service-basic;
      uses site-service-qos-profile;
      uses site-service-mpls;
      uses site-service-multicast;
      description
        "Service parameters on the attachment.";
    }
    description
      "Grouping for service parameters.";
  }

  grouping vpn-extranet {
    container extranet-vpns {
      if-feature "extranet-vpn";
      list extranet-vpn {
        key "vpn-id";
        leaf vpn-id {
          type svc-id;
          description
            "Identifies the target VPN the local VPN want to access.";
        }
        leaf local-sites-role {
          type identityref {
            base site-role;
          }
          default "any-to-any-role";
          description
            "This describes the role of the
             local sites in the target VPN topology.  In the any-to-any VPN
             service topology, the local sites must have the same role, which
             will be 'any-to-any-role'.  In the Hub-and-Spoke VPN service
             topology or the Hub-and-Spoke disjoint VPN service topology,
             the local sites must have a Hub role or a Spoke role.";
        }
        description
          "List of extranet VPNs or target VPNs the local VPN is
           attached to.";
      }
      description
        "Container for extranet VPN configuration.";
    }
    description
      "Grouping for extranet VPN configuration.
       This provides an easy way to interconnect
       all sites from two VPNs.";
  }

  grouping site-attachment-availability {
    container availability {
      leaf access-priority {
        type uint32;
        default "100";
        description
          "Defines the priority for the access.
           The higher the access-priority value,
           the higher the preference of the
           access will be.";
      }
      description
        "Availability parameters (used for multihoming).";
    }
    description
      "Defines availability parameters for a site.";
  }

  grouping access-vpn-policy {
    container vpn-attachment {
      choice attachment-flavor {
        case vpn-policy-id {
          leaf vpn-policy-id {
            type leafref {
              path "../../../../"
                 + "vpn-policies/vpn-policy/"
                 + "vpn-policy-id";
            }
            description
              "Reference to a VPN policy.  When referencing VPN
               policy for attachment, the vpn-policy-id must be
               configured.";
          }
        }
        case vpn-id {
          leaf vpn-id {
            type leafref {
              path "/l3vpn-svc/vpn-services"
                 + "/vpn-service/vpn-id";
            }
            description
              "Reference to an IP VPN.  Referencing a vpn-id provides
               an easy way to attach a particular logical access to
               a VPN.  In this case, vpn-id must be configured.";
          }
          leaf site-role {
            type identityref {
              base site-role;
            }
            default "any-to-any-role";
            description
              "Role of the site in the IP VPN.  When referencing a vpn-id,
               the site-role setting must be added to express the role of
                   the site in the target VPN service topology.";
          }
        }
        mandatory true;
        description
          "Choice for VPN attachment flavor.  A choice is implemented
           to allow the user to choose the flavor that provides the
           best fit.";
      }
      description
        "Defines VPN attachment of a site.";
    }
    description
      "Defines the VPN attachment rules for
       a site's logical access.";
  }

  grouping vpn-profile-cfg {
    container valid-provider-identifiers {
      list cloud-identifier {
        if-feature "cloud-access";
        key "id";
        leaf id {
          type string;
          description
            "Identification of cloud service.
             Local administration meaning.";
        }
        description
          "List for Cloud Identifiers.";
      }
      list encryption-profile-identifier {
        key "id";
        leaf id {
          type string;
          description
            "Identification of the SP encryption profile
             to be used.  Local administration meaning.";
        }
        description
          "List for encryption profile identifiers.";
      }
      list qos-profile-identifier {
        key "id";
        leaf id {
          type string;
          description
            "Identification of the QoS Profile to be used.
             Local administration meaning.";
        }
        description
          "List for QoS Profile Identifiers.";
      }
      list bfd-profile-identifier {
        key "id";
        leaf id {
          type string;
          description
            "Identification of the SP BFD Profile to be used.
             Local administration meaning.";
        }
        description
          "List for BFD Profile identifiers.";
      }
      nacm:default-deny-write;
      description
        "Container for Valid Provider Identifies.";
    }
    description
      "Grouping for VPN Profile configuration.";
  }

  grouping vpn-svc-cfg {
    leaf vpn-id {
      type svc-id;
      description
        "VPN identifier.  Local administration meaning.";
    }
    leaf customer-name {
      type string;
      description
        "Name of the customer that actually uses the VPN service.
         In the case that any intermediary (e.g., Tier-2 provider
         or partner) sells the VPN service to their end user
         on behalf of the original service provider (e.g., Tier-1
         provider), the original service provider may require the
         customer name to provide smooth activation/commissioning
         and operation for the service.";
    }
    leaf vpn-service-topology {
      type identityref {
        base vpn-topology;
      }
      default "any-to-any";
      description
        "VPN service topology.";
    }
    uses vpn-service-cloud-access;
    uses vpn-service-multicast;
    uses vpn-service-mpls;
    uses vpn-extranet;
    description
      "Grouping for VPN service configuration.";
  }

  grouping site-top-level-cfg {
    uses operational-requirements;
    uses customer-location-info;
    uses site-devices;
    uses site-diversity;
    uses site-management;
    uses site-vpn-policy;
    uses site-vpn-flavor;
    uses site-maximum-routes;
    uses site-security;
    uses site-service;
    uses site-protection;
    uses site-routing;
    description
      "Grouping for site top-level configuration.";
  }

  grouping site-network-access-top-level-cfg {
    leaf site-network-access-type {
      type identityref {
        base site-network-access-type;
      }
      default "point-to-point";
      description
        "Describes the type of connection, e.g.,
         point-to-point or multipoint.";
    }
    choice location-flavor {
      case location {
        when "derived-from-or-self(../../management/type, "
           + "'l3vpn-svc:customer-managed')" {
          description
            "Applicable only for customer-managed device.";
        }
        leaf location-reference {
          type leafref {
            path "../../../locations/location/location-id";
          }
          description
            "Location of the site-network-access.";
        }
      }
      case device {
        when "derived-from-or-self(../../management/type, "
           + "'l3vpn-svc:provider-managed') or "
           + "derived-from-or-self(../../management/type, "
           + "'l3vpn-svc:co-managed')" {
          description
            "Applicable only for provider-managed or co-managed device.";
        }
        leaf device-reference {
          type leafref {
            path "../../../devices/device/device-id";
          }
          description
            "Identifier of CE to use.";
        }
      }
      mandatory true;
      description
        "Choice of how to describe the site's location.";
    }
    uses access-diversity;
    uses site-attachment-bearer;
    uses site-attachment-ip-connection;
    uses site-security;
    uses site-network-access-service;
    uses site-routing;
    uses site-attachment-availability;
    uses access-vpn-policy;
    description
      "Grouping for site network access top-level configuration.";
  }

  /* Main blocks */

  container l3vpn-svc {
    container vpn-profiles {
      uses vpn-profile-cfg;
      description
        "Container for VPN Profiles.";
    }
    container vpn-services {
      list vpn-service {
        key "vpn-id";
        uses vpn-svc-cfg;
        description
          "List of VPN services.";
      }
      description
        "Top-level container for the VPN services.";
    }
    container sites {
      list site {
        key "site-id";
        leaf site-id {
          type svc-id;
          description
            "Identifier of the site.";
        }
        uses site-top-level-cfg;
        uses operational-requirements-ops;
        container site-network-accesses {
          list site-network-access {
            key "site-network-access-id";
            leaf site-network-access-id {
              type svc-id;
              description
                "Identifier for the access.";
            }
            uses site-network-access-top-level-cfg;
            description
              "List of accesses for a site.";
          }
          description
            "List of accesses for a site.";
        }
        description
          "List of sites.";
      }
      description
        "Container for sites.";
    }
    description
      "Main container for L3VPN service configuration.";
  }
}
