module ietf-l2-topology {
  yang-version 1.1;
  namespace "urn:ietf:params:xml:ns:yang:ietf-l2-topology";
  prefix l2t;

  import ietf-network {
    prefix nw;
    reference
      "RFC 8345: A YANG Data Model for Network Topologies";
  }
  import ietf-network-topology {
    prefix nt;
    reference
      "RFC 8345: A YANG Data Model for Network Topologies";
  }
  import ietf-inet-types {
    prefix inet;
    reference
      "RFC 6991:Common YANG Data Types";
  }
  import ietf-yang-types {
    prefix yang;
    reference
      "RFC 6991:Common YANG Data Types";
  }
  import iana-if-type {
    prefix ianaift;
    reference
      "RFC 7224: IANA Interface Type YANG Module";
  }
  import ieee802-dot1q-types {
    prefix dot1q-types;
    reference
      "IEEE Std 802.1Qcp-2018: Bridges and Bridged
       Networks - Amendment: YANG Data Model";
  }

  organization
    "IETF I2RS (Interface to the Routing System) Working Group";
  contact
    "WG Web:   <https://datatracker.ietf.org/wg/i2rs>
     WG List:  <mailto:i2rs@ietf.org>

     Editor:    Jie Dong
               <mailto:jie.dong@huawei.com>

     Editor:    Xiugang Wei
               <mailto:weixiugang@huawei.com>

     Editor:    Qin Wu
               <mailto:bill.wu@huawei.com>

     Editor:    Mohamed Boucadair
               <mailto:mohamed.boucadair@orange.com>

     Editor:    Anders Liu
               <mailto:andersliu@tencent.com>";
  description
    "This module defines a basic model for the Layer 2 topology
     of a network.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 8944; see
     the RFC itself for full legal notices.";

  revision 2020-11-15 {
    description
      "Initial revision.";
    reference
      "RFC 8944: A YANG Data Model for Layer 2 Network Topologies";
  }

  feature VLAN {
    description
      "Enables VLAN tag support as defined in IEEE 802.1Q.";
    reference
      "IEEE Std 802.1Q-2014: Bridges and Bridged Networks";
  }

  feature QinQ {
    description
      "Enables QinQ double tag support as defined in IEEE 802.1ad.";
    reference
      "IEEE Std 802.1ad: Provider Bridges";
  }

  feature VXLAN {
    description
      "Enables VXLAN support as defined in RFC 7348.";
    reference
      "RFC 7348: Virtual eXtensible Local Area Network (VXLAN):
                 A Framework for Overlaying Virtualized Layer 2
                 Networks over Layer 3 Networks";
  }

  identity flag-identity {
    description
      "Base type for flags.";
  }

  identity eth-encapsulation-type {
    base ianaift:iana-interface-type;
    description
      "Base identity from which specific Ethernet
       encapsulation types are derived.";
    reference
      "RFC 7224: IANA Interface Type YANG Module";
  }

  identity ethernet {
    base eth-encapsulation-type;
    description
      "Native Ethernet encapsulation.";
  }

  identity vlan {
    base eth-encapsulation-type;
    description
      "VLAN encapsulation.";
  }

  identity qinq {
    base eth-encapsulation-type;
    description
      "QinQ encapsulation.";
  }

  identity pbb {
    base eth-encapsulation-type;
    description
      "Provider Backbone Bridging (PBB) encapsulation.
       The PBB functions are developed in IEEE 802.1ah.";
  }

  identity trill {
    base eth-encapsulation-type;
    description
      "Transparent Interconnection of Lots of Links (TRILL)
       encapsulation.";
  }

  identity vpls {
    base eth-encapsulation-type;
    description
      "Ethernet Virtual Private LAN Service (VPLS)
       interface encapsulation.";
  }

  identity vxlan {
    base eth-encapsulation-type;
    description
      "VXLAN Media Access Control (MAC) in UDP encapsulation.";
    reference
      "RFC 7348: Virtual eXtensible Local Area  Network (VXLAN):
                 A Framework for Overlaying Virtualized Layer 2
                 Networks over Layer 3 Networks";
  }

  typedef vni {
    type uint32 {
      range "0..16777215";
    }
    description
      "VXLAN Network Identifier or VXLAN Segment ID.
       It allows up to 16 M VXLAN segments to coexist
       within the same administrative domain.

       The use of value '0' is implementation specific.";
    reference
      "RFC 7348: Virtual eXtensible Local Area  Network (VXLAN):
                 A Framework for Overlaying Virtualized Layer 2
                 Networks over Layer 3 Networks";
  }

  typedef l2-flag-type {
    type identityref {
      base flag-identity;
    }
    description
      "Base type for L2 flags. One example of L2 flag
       type is trill, which represents the trill topology
       type.";
  }

  typedef node-flag-type {
    type identityref {
      base flag-identity;
    }
    description
      "Node flag attributes.  The physical node can be
       one example of a node flag attribute.";
  }

  typedef link-flag-type {
    type identityref {
      base flag-identity;
    }
    description
      "Link flag attributes.  One example of a link flag
       attribute is the pseudowire.";
  }

  typedef l2-network-event-type {
    type enumeration {
      enum addition {
        value 0;
        description
          "A Layer 2 node or link or termination-point
           has been added.";
      }
      enum removal {
        value 1;
        description
          "A Layer 2 node or link or termination-point
           has been removed.";
      }
      enum update {
        value 2;
        description
          "A Layer 2 node or link or termination-point
           has been updated.";
      }
    }
    description
      "Layer 2 network event type for notifications.";
  }

  typedef duplex-mode {
    type enumeration {
      enum full-duplex {
        description
          "Indicates full-duplex mode.";
      }
      enum half-duplex {
        description
          "Indicates half-duplex mode.";
      }
    }
    description
      "Indicates the type of the duplex mode.";
  }

  grouping l2-network-type {
    description
      "Indicates the topology type to be L2.";
    container l2-topology {
      presence "Indicates L2 Network Topology.";
      description
        "The presence of the container node indicates
         L2 Network Topology.";
    }
  }

  grouping l2-topology-attributes {
    description
      "L2 topology scope attributes.";
    container l2-topology-attributes {
      description
        "Contains L2 topology attributes.";
      leaf name {
        type string;
        description
          "Name of the topology.";
      }
      leaf-list flags {
        type l2-flag-type;
        description
          "Topology flags.";
      }
    }
  }

  grouping l2-node-attributes {
    description
      "L2 node attributes.";
    container l2-node-attributes {
      description
        "Contains L2 node attributes.";
      leaf name {
        type string;
        description
          "Node name.";
      }
      leaf-list flags {
        type node-flag-type;
        description
          "Node flags.  It can be used to indicate
           node flag attributes.";
      }
      leaf-list bridge-id {
        type string {
          pattern '[0-9a-fA-F]{2}(:[0-9a-fA-F]{2}){7}';
        }
        description
          "This is the bridge identifier represented as a
           hexadecimal 8-octet string.  It has 4 bits of
           priority, 12 bits of Multiple Spanning Tree
           Instance Identifier (MSTI-ID), and the base bridge
           identifier.  There may be multiple for each
           spanning tree instance.";
        reference
          "RFC 7727: Spanning Tree Protocol (STP) Application of
                     the Inter-Chassis Communication Protocol
                     (ICCP)";
      }
      leaf-list management-address {
        type inet:ip-address;
        description
          "IP address used for management purpose.";
      }
      leaf management-mac {
        type yang:mac-address;
        description
          "This is a MAC address used for the bridge management.
           It can be the Bridge Base VLAN ID (VID), interface
           MAC address, or other. ";
      }
      leaf management-vlan {
        type string;
        description
          "This is a VLAN that supports the management address.
           The actual VLAN ID type and value would be a member of
           this VLAN.";
      }
    }
  }

  grouping l2-link-attributes {
    description
      "L2 link attributes.";
    container l2-link-attributes {
      description
        "Contains L2 link attributes.";
      leaf name {
        type string;
        description
          "Link name.";
      }
      leaf-list flags {
        type link-flag-type;
        description
          "Link flags.  It can be used to indicate
           link flag attributes.";
      }
      leaf rate {
        type uint64;
        units "Kbps";
        description
          "Link rate.  It specifies bandwidth requirements
           associated with the specific link.  The link
           contains a source and a destination.";
      }
      leaf delay {
        type uint32;
        units "microseconds";
        description
          "Unidirectional link delay in
           microseconds.";
      }
      leaf auto-nego {
        type boolean;
        default "true";
        description
          "Set to true if auto-negotiation is supported.
           Set to false if auto-negotiation is not supported.";
      }
      leaf duplex {
        type duplex-mode;
        description
          "Exposes the duplex mode, full-duplex or half-duplex.";
      }
    }
  }

  grouping l2-termination-point-attributes {
    description
      "L2 termination point attributes.";
    container l2-termination-point-attributes {
      description
        "Containing L2 termination point attributes.";
      leaf interface-name {
        type string;
        description
          "Name of the interface.  The name can (but does not
           have to) correspond to an interface reference of a
           containing node's interface, i.e., the path name of a
           corresponding interface data node on the containing
           node is reminiscent of data type interface-ref defined
           in RFC 8343.  It should be noted that data type
           interface-ref of RFC 8343 cannot be used directly,
           as this data type is used to reference an interface
           in a datastore of a single node in the network, not
           to uniquely reference interfaces across a network.";
      }
      leaf mac-address {
        type yang:mac-address;
        description
          "Interface MAC address for logical link control.";
      }
      leaf-list port-number {
        type uint32;
        description
          " List of port numbers of the bridge ports for which each
            entry contains bridge management information.";
      }
      leaf-list unnumbered-id {
        type uint32;
        description
          "List of unnumbered interface identifiers.
           The unnumbered interface identifier will correspond to
           the ifIndex value of the interface, i.e., the ifIndex
           value of the ifEntry that represents the interface in
           implementations where the Interfaces Group MIB
           (RFC 2863) is supported.";
      }
      leaf encapsulation-type {
        type identityref {
          base eth-encapsulation-type;
        }
        description
          "Encapsulation type of this
                 termination point.";
      }
      leaf outer-tag {
        if-feature "VLAN";
        type dot1q-types:vid-range-type;
        description
          "The outermost VLAN tag.  It may include a list of VLAN
           Ids or nonoverlapping VLAN ranges.";
      }
      leaf outer-tpid {
        if-feature "QinQ";
        type dot1q-types:dot1q-tag-type;
        description
          "Identifies a specific 802.1Q tag type of outermost VLAN
           tag.";
      }
      leaf inner-tag {
        if-feature "VLAN";
        type dot1q-types:vid-range-type;
        description
          "The inner VLAN tag.  It may include a list of VLAN
           Ids or nonoverlapping VLAN ranges.";
      }
      leaf inner-tpid {
        if-feature "QinQ";
        type dot1q-types:dot1q-tag-type;
        description
          "Identifies a specific 802.1Q tag type of inner VLAN tag.";
      }
      leaf lag {
        type boolean;
        default "false";
        description
          "Defines whether lag is supported or not.
           When it is set to true, the lag is supported.";
      }
      leaf-list member-link-tp {
        when "../lag = 'true'" {
          description
            "Relevant only when the lag interface is supported.";
        }
        type leafref {
          path "/nw:networks/nw:network/nw:node"
             + "/nt:termination-point/nt:tp-id";
        }
        description
          "List of member link termination points associated with
           specific L2 termination point.";
      }
      container vxlan {
        when "derived-from-or-self(../encapsulation-type, "
           + "'l2t:vxlan')" {
          description
            "Only applies when the type of the Ethernet
             encapsulation is 'vxlan'.";
        }
        if-feature "VXLAN";
        leaf vni-id {
          type vni;
          description
            "VXLAN Network Identifier (VNI).";
        }
        description
          "Vxlan encapsulation type.";
      }
    }
  }

  augment "/nw:networks/nw:network/nw:network-types" {
    description
      "Introduces new network type for L2 topology.";
    uses l2-network-type;
  }

  augment "/nw:networks/nw:network" {
    when '/nw:networks/nw:network/nw:network-types/l2t:l2-topology' {
      description
        "Augmentation parameters apply only for networks
         with L2 topology.";
    }
    description
      "Configuration parameters for the L2 network
       as a whole.";
    uses l2-topology-attributes;
  }

  augment "/nw:networks/nw:network/nw:node" {
    when '/nw:networks/nw:network/nw:network-types/l2t:l2-topology' {
      description
        "Augmentation parameters apply only for networks
         with L2 topology.";
    }
    description
      "Configuration parameters for L2 at the node
       level.";
    uses l2-node-attributes;
  }

  augment "/nw:networks/nw:network/nt:link" {
    when '/nw:networks/nw:network/nw:network-types/l2t:l2-topology' {
      description
        "Augmentation parameters apply only for networks
         with L2 topology.";
    }
    description
      "Augments L2 topology link information.";
    uses l2-link-attributes;
  }

  augment "/nw:networks/nw:network/nw:node/nt:termination-point" {
    when '/nw:networks/nw:network/nw:network-types/l2t:l2-topology' {
      description
        "Augmentation parameters apply only for networks
         with L2 topology.";
    }
    description
      "Augments L2 topology termination point information.";
    uses l2-termination-point-attributes;
  }

  notification l2-node-event {
    description
      "Notification event for L2 node.";
    leaf event-type {
      type l2-network-event-type;
      description
        "Event type.";
    }
    uses nw:node-ref;
    uses l2-network-type;
    uses l2-node-attributes;
  }

  notification l2-link-event {
    description
      "Notification event for L2 link.";
    leaf event-type {
      type l2-network-event-type;
      description
        "Event type.";
    }
    uses nt:link-ref;
    uses l2-network-type;
    uses l2-link-attributes;
  }

  notification l2-termination-point-event {
    description
      "Notification event for L2 termination point.";
    leaf event-type {
      type l2-network-event-type;
      description
        "Event type.";
    }
    uses nt:tp-ref;
    uses l2-network-type;
    uses l2-termination-point-attributes;
  }
}
